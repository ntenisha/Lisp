;(progn(zd1333)(zd118)(vla-save(vla-get-activedocument(vlax-get-acad-object)))(VL-CMDF "_close"))

;(progn(zd1333)(vla-save(vla-get-activedocument(vlax-get-acad-object)))(VL-CMDF "_close"))

;(command "-graphicsconfig" "acceleration" "hardware" "exit")
